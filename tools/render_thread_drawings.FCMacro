"""Regenerate the nine annotated PNGs from the matching production STEP files."""
from pathlib import Path

script = Path(__file__).resolve().with_suffix('.py')
namespace = {'__file__': str(script), '__name__': 'thread_drawing_renderer'}
exec(compile(script.read_text(encoding='utf-8'), str(script), 'exec'), namespace)
namespace['render'](script.parents[1])
